HOST-RESOURCES-MIB DEFINITIONS ::= BEGIN

IMPORTS
    MODULE-IDENTITY, OBJECT-TYPE, Integer32, Gauge32
        FROM SNMPv2-SMI
    DisplayString, TimeStamp
        FROM SNMPv2-TC;

hostResourcesMibModule MODULE-IDENTITY
    LAST-UPDATED "200001010000Z"
    ORGANIZATION "IETF"
    CONTACT-INFO "ietf.org"
    DESCRIPTION "The MIB for host resources."
    ::= { mib-2 25 }

hrSystem        OBJECT IDENTIFIER ::= { hostResourcesMibModule 1 }
hrStorage       OBJECT IDENTIFIER ::= { hostResourcesMibModule 2 }
hrDevice        OBJECT IDENTIFIER ::= { hostResourcesMibModule 3 }
hrSWRun         OBJECT IDENTIFIER ::= { hostResourcesMibModule 4 }

hrSystemUptime OBJECT-TYPE
    SYNTAX      Integer32
    MAX-ACCESS  read-only
    STATUS      current
    DESCRIPTION "The amount of time since this host was last initialized."
    ::= { hrSystem 1 }

hrSystemNumUsers OBJECT-TYPE
    SYNTAX      Gauge32
    MAX-ACCESS  read-only
    STATUS      current
    DESCRIPTION "The number of user sessions for which this host is storing state."
    ::= { hrSystem 5 }

hrStorageTable OBJECT-TYPE
    SYNTAX      SEQUENCE OF HrStorageEntry
    MAX-ACCESS  not-accessible
    STATUS      current
    DESCRIPTION "The (conceptual) table of logical storage areas on the host."
    ::= { hrStorage 3 }

hrStorageEntry OBJECT-TYPE
    SYNTAX      HrStorageEntry
    MAX-ACCESS  not-accessible
    STATUS      current
    DESCRIPTION "A (conceptual) entry for one logical storage area."
    ::= { hrStorageTable 1 }

hrStorageDescr OBJECT-TYPE
    SYNTAX      DisplayString
    MAX-ACCESS  read-only
    STATUS      current
    DESCRIPTION "A description of the type and instance of the storage described by this entry."
    ::= { hrStorageEntry 3 }

hrStorageSize OBJECT-TYPE
    SYNTAX      Integer32
    MAX-ACCESS  read-write
    STATUS      current
    DESCRIPTION "The size of the storage represented by this entry, in units of hrStorageAllocationUnits."
    ::= { hrStorageEntry 5 }

hrStorageUsed OBJECT-TYPE
    SYNTAX      Integer32
    MAX-ACCESS  read-only
    STATUS      current
    DESCRIPTION "The amount of the storage represented by this entry that is allocated, in units of hrStorageAllocationUnits."
    ::= { hrStorageEntry 6 }

hrDeviceTable OBJECT-TYPE
    SYNTAX      SEQUENCE OF HrDeviceEntry
    MAX-ACCESS  not-accessible
    STATUS      current
    DESCRIPTION "The (conceptual) table of devices contained by the host."
    ::= { hrDevice 2 }

hrDeviceEntry OBJECT-TYPE
    SYNTAX      HrDeviceEntry
    MAX-ACCESS  not-accessible
    STATUS      current
    DESCRIPTION "A (conceptual) entry for one device contained by the host."
    ::= { hrDeviceTable 1 }

hrDeviceDescr OBJECT-TYPE
    SYNTAX      DisplayString
    MAX-ACCESS  read-only
    STATUS      current
    DESCRIPTION "A textual description of this device, including the device's manufacturer and revision."
    ::= { hrDeviceEntry 2 }

hrDeviceType OBJECT-TYPE
    SYNTAX      OBJECT IDENTIFIER
    MAX-ACCESS  read-only
    STATUS      current
    DESCRIPTION "The type of this device."
    ::= { hrDeviceEntry 3 }

hrProcessorTable OBJECT-TYPE
    SYNTAX      SEQUENCE OF HrProcessorEntry
    MAX-ACCESS  not-accessible
    STATUS      current
    DESCRIPTION "The (conceptual) table of processors contained by the host."
    ::= { hrDevice 3 }

hrProcessorEntry OBJECT-TYPE
    SYNTAX      HrProcessorEntry
    MAX-ACCESS  not-accessible
    STATUS      current
    DESCRIPTION "A (conceptual) entry for one processor contained by the host."
    ::= { hrProcessorTable 1 }

hrProcessorLoad OBJECT-TYPE
    SYNTAX      Integer32 (0..100)
    MAX-ACCESS  read-only
    STATUS      current
    DESCRIPTION "The average, over the last minute, of the percentage of time that this processor was not idle. Implementations may approximate this one minute sampling period with different amounts of time."
    ::= { hrProcessorEntry 2 }

hrSWRunTable OBJECT-TYPE
    SYNTAX      SEQUENCE OF HrSWRunEntry
    MAX-ACCESS  not-accessible
    STATUS      current
    DESCRIPTION "The (conceptual) table of software running on the host."
    ::= { hrSWRun 2 }

hrSWRunEntry OBJECT-TYPE
    SYNTAX      HrSWRunEntry
    MAX-ACCESS  not-accessible
    STATUS      current
    DESCRIPTION "A (conceptual) entry for one piece of software running on the host."
    ::= { hrSWRunTable 1 }

hrSWRunName OBJECT-TYPE
    SYNTAX      DisplayString
    MAX-ACCESS  read-only
    STATUS      current
    DESCRIPTION "The name of this running piece of software."
    ::= { hrSWRunEntry 2 }

END
